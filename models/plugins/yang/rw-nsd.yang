/*
 * 
 *   Copyright 2016-2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-nsd
{
  namespace "http://riftio.com/ns/riftware-1.0/rw-nsd";
  prefix "rw-nsd";

  import rw-nsd-base {
    prefix "rw-nsd-base";
  }

  import nsd {
    prefix "nsd";
  }

  revision 2017-02-28 {
    description
      "Update model to support projects.";
  }

  revision 2015-09-10 {
    description
      "Initial revision. This YANG file augments
       the base MANO NSD";
    reference
      "Derived from earlier versions of base YANG files";
  }

  augment /nsd:nsd-catalog/nsd:nsd {
    uses rw-nsd-base:rw-nsd-ext;
  }
}

// vim: sw=2
