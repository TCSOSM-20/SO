/*
 * 
 *   Copyright 2016-2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-vnfd
{
  namespace "http://riftio.com/ns/riftware-1.0/rw-vnfd";
  prefix "rw-vnfd";

  import vnfd {
    prefix "vnfd";
  }

  import rw-vnfd-base {
    prefix "rw-vnfd-base";
  }

  revision 2017-02-28 {
    description
      "Update model to support projects.";
  }

  revision 2015-09-10 {
    description
      "Initial revision. This YANG file augments
       the base MANO VNFD";
    reference
      "Derived from earlier versions of base YANG files";
  }

  augment /vnfd:vnfd-catalog/vnfd:vnfd {
    uses rw-vnfd-base:rw-vnfd-ext;
  }

  augment /vnfd:vnfd-catalog/vnfd:vnfd/vnfd:vdu {
    uses rw-vnfd-base:vcs-component-ref;
  }
}
// vim: sw=2
