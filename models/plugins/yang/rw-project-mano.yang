/*
 *
 *   Copyright 2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 */

module rw-project-mano
{
  namespace "http://riftio.com/ns/riftware-1.0/rw-project-mano";
  prefix "rw-project-mano";

  import rw-pb-ext {
    prefix "rw-pb-ext";
  }

  import rw-project {
    prefix "rw-project";
  }

  revision 2017-03-08 {
    description
      "Initial revision. This YANG file defines the
       MANO extentions for project based tenancy";
    reference
      "Derived from earlier versions of base YANG files";
  }

  augment /rw-project:project/rw-project:project-config {
    leaf name-ref {
      type leafref {
        path "../../rw-project:name";
      }
    }
  }
}
