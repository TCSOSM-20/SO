/*
 * 
 *   Copyright 2016-2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-launchpad-annotation
{
  namespace "http://riftio.com/ns/riftware-1.0/rw-launchpad-annotation";
  prefix "rw-launchpad-ann";

  import rw-launchpad {
    prefix rw-launchpad;
  }

  import tailf-common {
    prefix tailf;
  }

  import rw-project {
    prefix "rw-project";
  }

  tailf:annotate "/rw-project:project/rw-launchpad:datacenters" {
    tailf:callpoint rw_callpoint;
  }
}
